(defun c:xxxxxx(/ a h1 b c d e f)
  (setq a (getpoint "enter a point:"))
  (setq h1 (getdist "\nh1:"))
  (setq b (polar a 0 h1))
  (setq c (polar b (/ pi 3) h1))
  (setq d (polar c (* 2 (/ pi 3)) h1))
  (setq e (polar d pi h1))
  (setq f (polar e (* 4 (/ pi 3)) h1))
  (command "pline" a b c d e f "c")
  (command "line" a e "")
  (command "line" a c "")
  (command "line" b f "")
  (command "line" b d "")
  (command "line" c e "")
  (command "line" f d "")(prin1)
 )
(defun c:xxx(/ a h1 b c d e f)
  (setvar "cmdecho" 0)
  (setq a (getpoint "enter a point:"))
  (setq h1 (getdist "\nh1:"))
  (setq b (polar a 0 h1))
  (setq c (polar b (/ pi 3) h1))
  (setq d (polar c (* 2 (/ pi 3)) h1))
  (setq e (polar d pi h1))
  (setq f (polar e (* 4 (/ pi 3)) h1))
  (command "pline" a b c d e f "c")(prin1)
)
(defun c:123(/ a b c r)
  (setq a '(15 10) b '(50 40) c'(60 15) r 12.5)
  (command "line" a b "")
  (command "circle" c r "")
  (command "dtext" '(0 0) 8 0 "")
  (prin1))
(defun c:1(/ e1 e1-1 o n)
  (setq e1 (entsel "请选择图形：") e1-1 (entget (car e1)))
  (setq o (assoc 40 e1-1))
  (setq n (cons 40 23.8))
  (setq e1-1 (subst n o e1-1))
  (entmod e1-1)
  (prin1))
(defun c:2(/ e1 e1-1 o n)
  (setq e1 (entsel "请选择图形:") e1-1 (entget (car e1)))
  (setq o (assoc 10 e1-1))
  (setq n (cons 10 '(100 20 0)))
  (setq e1-1 (subst n o e1-1))
  (entmod e1-1)
	(prin1))
(defun c:3(/ a1 a1-1 o n)
  (setq a1 (entsel "\n请选择图形：") a1-1 (entget (car a1)))
  (setq o (assoc 1 a1-1))
  (setq n (cons 1 "jiangziying"))
  (setq a1-1 (subst n o a1-1))
  (entmod a1-1)
  (prin1))
(defun c:4(/ a1 a1-1 r y n)
  (setvar "cmdecho" 0)
  (setq a1 (entsel "\n请选择图形：\n") a1-1 (entget (car a1)))
  (princ "图形信息如下\n：") (princ a1-1)
  (setq r (assoc 40 a1-1))
  (setq y (assoc 10 a1-1))
  (princ "\n半径：") (princ (cdr r))
  (princ "\n圆心：") (princ (cdr y))
  (setq n (cons 40 (getdist (cdr y) "\n新的半径：")))
  (setq a1-1 (subst n r a1-1))
  (entmod a1-1)
  (prin1))
(defun c:5()
  (setvar "cmdecho" 0)
  (setq a1 (entget (car (entsel "请选择图形："))))
  (setq a2 (cdr (assoc 11 a1)) a3 (cdr (assoc 10 a1)))
  (setq x1 (car a2) x2 (car a3) y1 (cadr a2) y2 (cadr a3))
  (setq c1 (* 0.5 (+ x1 x2)) c2 (* 0.5 (+ y1 y2)) c (list c1 c2 0))
  (command "circle" c (getdist c "请输入半径：\n"))
	   (prin1)
  )
(defun c:5-2()
  (setvar "cmdecho" 0)
  (setq a1 (cadr (entsel "请选择图形：")))
  (setq a1 (osnap a1 "mid"))
  (command "circle" a1 (getdist c "请输入半径：\n"))
	   (prin1)
  )
(defun c:6()
  (setvar "cmdecho" 0)
  (setq a1 (entsel "请选择图形：") a1-1 (entget (car a1)))
  (setq r (assoc 40 a1-1) c (assoc 10 a1-1))
  (setq r (cdr r) c (cdr c))
  (command "polygon" 5 c "c" r "")
  (prin1))
(defun c:7-1()
  (setvar "cmdecho" 0)
  (setq a (entsel "请选择图形："))
  (setq a1-1 (entget (car a)))
  (setq r (assoc 40 a1-1))
  (setq r1 (* 0.5 (cdr r)))
  (setq r1 (cons 40 r1))
  (setq a1-1 (subst r1 r a1-1))
  (entmod a1-1)
  (prin1))
(defun c:7-2()
  (setvar "cmdecho" 0)
  (setq a (entsel "请选择图形："))
  (setq a1-1 (entget (car a)))
  (setq r (assoc 40 a1-1))
  (setq r1 (* 2 (cdr r)))
  (setq r1 (cons 40 r1))
  (setq a1-1 (subst r1 r a1-1))
  (entmod a1-1)
  (prin1))
(defun c:8()
  (setvar "cmdecho" 0)
  (setq a (getpoint "请选择一点："))
  (setq w (getreal " \n请输入底边长：") x (getreal "\n请输入斜边长度："))
  (setq h (sqrt (- (* x x) (* w w))))
  (setq b (polar a 0 w))
  (setq c (polar a (/ pi 2) h))
  (command "pline" a c b "c")
  (setq ang1 (atan h w) ang2 (atan w h))
  (princ "\n高度=") (princ h) (princ "\n∠1=") (princ (* ang1 (/ 180 pi))) (princ "\n∠2=") (princ (* ang2 (/ 180 pi)))
	(prin1))
(defun c:9()
  (setvar "cmdecho" 0)
  (setq c (getpoint "请指定一点："))
  (setq r (getreal "\n请输入半径："))
  (setq n (getint "\n请输入数量："))
  (setq ang1 (/ (* 2 pi) (* 2 n)) ang2 (- (/ pi 2) ang1))
  (setq R (/ r (sin ang1)))
  (setq d (polar c ang2 R))
  (command "circle" c r)
  (command "array" (entlast) "" "p" d n 360 "y")
  (prin1))
(defun c:rect()
  (setq dcl_id (load_dialog "C:\\Users\\Administrator\\Desktop\\对话框代码练习\\RECT.DCL"))
  (new_dialog "RECT" dcl_id)
  (action_tile "accept" "(s_rect) (done_dialog)")
  (start_dialog) (unload_dialog dcl_id)
  (setq a (getpoint "请选择一点：")
	b (polar a 0 w)
	c (polar b (/ pi 2) h)
	d (polar c pi w))
  (command "pline" a b c d "c")
  (princ)
)
(defun s_rect()
    (setq w (atof (get_tile "rect_w")))
    (setq h (atof (get_tile "rect_h")))
  )
(defun c:29()
  (setq dcl_id (load_dialog "F:\\BaiduNetdiskDownload\\视频教程代码\\代码\\29\\29demo.DCL"))
  (new_dialog "demo1" dcl_id)
  (start_dialog) (unload_dialog dcl_id))
(defun c:rect()
  (setvar "cmdecho" 0)
  (setq dcl_id (load_dialog "C:\\Users\\Administrator\\Desktop\\对话框代码练习\\RECT.DCL"))
  (new_dialog "RECT" dcl_id)
  (action_tile "accept" "(s_rect) (done_dialog)")
  (action_tile "rect_e" "(mode_tile \"rect_x\" 0)")
  (action_tile "rect_d" "(mode_tile \"rect_x\" 1)")
  (action_tile "n" "(setq t1 (get_tile \"n\")) (set_tile \"s\" t1) (set_tile \"t\" t1)")
  (action_tile "s" "(setq t2 (get_tile \"s\")) (set_tile \"t\" t2) (set_tile \"n\" t2)")
  (start_dialog) (unload_dialog dcl_id)
  (setq a (getpoint "\n选一点："))
  (setq b (polar a 0 w) c (polar b (/ pi 2) h) d (polar a (/ pi 2) h))
  (command "pline" a b c d "c")
  (if (= x 1) (command "line" a c "" "line" b d ""))
  (if (= gs 1) (command "copy" (entlast) a b "c"))
  (prin1))
(defun s_rect()
  (setq w (abs (atof (get_tile "rect_w")))
	h (abs (atof (get_tile "rect_h")))
	x (atoi (get_tile "rect_x"))
	gs (atoi (get_tile "gs"))))
