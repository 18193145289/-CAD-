(defun c:1111()
  (setvar "cmdecho" 0)
  (setvar "osmode" 0)
  (setq bl (getstring "输入比例<1>:\n") bl (atof bl) ori (getstring "方向<n>:\n"))
  (if (= bl 0)
    (setq bl 1))
  (if (= ori "n")
    (progn
  (setq a1 (getpoint "d1:\n") a2 (getpoint "d2:\n"))
  (command "pline" a1 "w" (* 0.2 bl) "" a2 "") (setq s (entlast))
  (command "ucs" "ob" s)
  (setq a1 (getpoint "d1:\n") a2 (getpoint "d2:\n") a4 (polar a1 0 (* 6 bl)) b1 (polar a4 0 (* 5 bl)) a3 (list (/ (+ (car a4) (car b1)) 2) (/ (+ (cadr a4) (cadr b1)) 2)) b2 (polar b1 (* 3 (/ pi 2)) (* 1 bl)) b3 (polar b2 0 (* 4 bl)) b4 (polar a3 (* 3 (/ pi 2)) (* 3 bl)) b5 (polar a4 (* 3 (/ pi 2)) (* 1 bl)) b6 (polar b5 pi (* 4 bl)))
  (command "erase" s "")
  (command "pline" a1 "w" (* 0.2 bl) "" b1 b2 b3 b4 b6 b5 a4 "") (setq ss (entlast))
  (command "pline" a1 "w" (* 0.2 bl) "" a2 "") (setq s (entlast))
  (setq a4 (polar a2 0 (-(* 6 bl))) b1 (polar a4 0 (-(* 5 bl))) a3 (list (/ (+ (car a4) (car b1)) 2) (/ (+ (cadr a4) (cadr b1)) 2)) b2 (polar b1 (* 3 (/ pi 2)) (* 1 bl)) b3 (polar b2 0 (-(* 4 bl))) b4 (polar a3 (* 3 (/ pi 2)) (* 3 bl)) b5 (polar a4 (* 3 (/ pi 2)) (* 1 bl)) b6 (polar b5 pi (-(* 4 bl))))
  (command "pline" a2 "w" (* 0.2 bl) "" b1 b2 b3 b4 b6 b5 a4 "") (setq sss (entlast))
  (command "pedit" "m" s ss sss "" "j" "" "")))
  (if (= ori "N")
    (progn
  (setq a1 (getpoint "d1:\n") a2 (getpoint "d2:\n"))
  (command "pline" a1 "w" (* 0.2 bl) "" a2 "") (setq s (entlast))
  (command "ucs" "ob" s)
  (setq a1 (getpoint "d1:\n") a2 (getpoint "d2:\n") a4 (polar a1 0 (* 6 bl)) b1 (polar a4 0 (* 5 bl)) a3 (list (/ (+ (car a4) (car b1)) 2) (/ (+ (cadr a4) (cadr b1)) 2)) b2 (polar b1 (* 3 (/ pi 2)) (* 1 bl)) b3 (polar b2 0 (* 4 bl)) b4 (polar a3 (* 3 (/ pi 2)) (* 3 bl)) b5 (polar a4 (* 3 (/ pi 2)) (* 1 bl)) b6 (polar b5 pi (* 4 bl)))
  (command "erase" s "")
  (command "pline" a1 "w" (* 0.2 bl) "" b1 b2 b3 b4 b6 b5 a4 "") (setq ss (entlast))
  (command "pline" a1 "w" (* 0.2 bl) "" a2 "") (setq s (entlast))
  (setq a4 (polar a2 0 (-(* 6 bl))) b1 (polar a4 0 (-(* 5 bl))) a3 (list (/ (+ (car a4) (car b1)) 2) (/ (+ (cadr a4) (cadr b1)) 2)) b2 (polar b1 (* 3 (/ pi 2)) (* 1 bl)) b3 (polar b2 0 (-(* 4 bl))) b4 (polar a3 (* 3 (/ pi 2)) (* 3 bl)) b5 (polar a4 (* 3 (/ pi 2)) (* 1 bl)) b6 (polar b5 pi (-(* 4 bl))))
  (command "pline" a2 "w" (* 0.2 bl) "" b1 b2 b3 b4 b6 b5 a4 "") (setq sss (entlast))
  (command "pedit" "m" s ss sss "" "j" "" "")))
  (if (= ori "")
    (progn
  (setq a1 (getpoint "d1:\n") a2 (getpoint "d2:\n"))
  (command "pline" a1 "w" (* 0.2 bl) "" a2 "") (setq s (entlast))
  (command "ucs" "ob" s)
  (setq a1 (getpoint "d1:\n") a2 (getpoint "d2:\n") a4 (polar a1 0 (* 6 bl)) b1 (polar a4 0 (* 5 bl)) a3 (list (/ (+ (car a4) (car b1)) 2) (/ (+ (cadr a4) (cadr b1)) 2)) b2 (polar b1 (* 3 (/ pi 2)) (* 1 bl)) b3 (polar b2 0 (* 4 bl)) b4 (polar a3 (* 3 (/ pi 2)) (* 3 bl)) b5 (polar a4 (* 3 (/ pi 2)) (* 1 bl)) b6 (polar b5 pi (* 4 bl)))
  (command "erase" s "")
  (command "pline" a1 "w" (* 0.2 bl) "" b1 b2 b3 b4 b6 b5 a4 "") (setq ss (entlast))
  (command "pline" a1 "w" (* 0.2 bl) "" a2 "") (setq s (entlast))
  (setq a4 (polar a2 0 (-(* 6 bl))) b1 (polar a4 0 (-(* 5 bl))) a3 (list (/ (+ (car a4) (car b1)) 2) (/ (+ (cadr a4) (cadr b1)) 2)) b2 (polar b1 (* 3 (/ pi 2)) (* 1 bl)) b3 (polar b2 0 (-(* 4 bl))) b4 (polar a3 (* 3 (/ pi 2)) (* 3 bl)) b5 (polar a4 (* 3 (/ pi 2)) (* 1 bl)) b6 (polar b5 pi (-(* 4 bl))))
  (command "pline" a2 "w" (* 0.2 bl) "" b1 b2 b3 b4 b6 b5 a4 "") (setq sss (entlast))
  (command "pedit" "m" s ss sss "" "j" "" "")))
  (if (= ori "y")
    (progn
  (setq a1 (getpoint "d1:\n") a2 (getpoint "d2:\n"))
  (command "pline" a1 "w" (* 0.2 bl) "" a2 "") (setq s (entlast))
  (command "ucs" "ob" s)
  (setq a1 (getpoint "d1:\n") a2 (getpoint "d2:\n") a4 (polar a1 0 (* 6 bl)) b1 (polar a4 0 (* 5 bl)) a3 (list (/ (+ (car a4) (car b1)) 2) (/ (+ (cadr a4) (cadr b1)) 2)) b2 (polar b1 (/ pi 2) (* 1 bl)) b3 (polar b2 0 (* 4 bl)) b4 (polar a3 (/ pi 2) (* 3 bl)) b5 (polar a4 (/ pi 2) (* 1 bl)) b6 (polar b5 pi (* 4 bl)))
  (command "erase" s "")
  (command "pline" a1 "w" (* 0.2 bl) "" b1 b2 b3 b4 b6 b5 a4 "") (setq ss (entlast))
  (command "pline" a1 "w" (* 0.2 bl) "" a2 "") (setq s (entlast))
  (setq a4 (polar a2 0 (-(* 6 bl))) b1 (polar a4 0 (-(* 5 bl))) a3 (list (/ (+ (car a4) (car b1)) 2) (/ (+ (cadr a4) (cadr b1)) 2)) b2 (polar b1 (/ pi 2) (* 1 bl)) b3 (polar b2 0 (-(* 4 bl))) b4 (polar a3 (/ pi 2) (* 3 bl)) b5 (polar a4 (/ pi 2) (* 1 bl)) b6 (polar b5 pi (-(* 4 bl))))
  (command "pline" a2 "w" (* 0.2 bl) "" b1 b2 b3 b4 b6 b5 a4 "") (setq sss (entlast))
  (command "pedit" "m" s ss sss "" "j" "" "")))
  (if (= ori "Y")
    (progn
  (setq a1 (getpoint "d1:\n") a2 (getpoint "d2:\n"))
  (command "pline" a1 "w" (* 0.2 bl) "" a2 "") (setq s (entlast))
  (command "ucs" "ob" s)
  (setq a1 (getpoint "d1:\n") a2 (getpoint "d2:\n") a4 (polar a1 0 (* 6 bl)) b1 (polar a4 0 (* 5 bl)) a3 (list (/ (+ (car a4) (car b1)) 2) (/ (+ (cadr a4) (cadr b1)) 2)) b2 (polar b1 (/ pi 2) (* 1 bl)) b3 (polar b2 0 (* 4 bl)) b4 (polar a3 (/ pi 2) (* 3 bl)) b5 (polar a4 (/ pi 2) (* 1 bl)) b6 (polar b5 pi (* 4 bl)))
  (command "erase" s "")
  (command "pline" a1 "w" (* 0.2 bl) "" b1 b2 b3 b4 b6 b5 a4 "") (setq ss (entlast))
  (command "pline" a1 "w" (* 0.2 bl) "" a2 "") (setq s (entlast))
  (setq a4 (polar a2 0 (-(* 6 bl))) b1 (polar a4 0 (-(* 5 bl))) a3 (list (/ (+ (car a4) (car b1)) 2) (/ (+ (cadr a4) (cadr b1)) 2)) b2 (polar b1 (/ pi 2) (* 1 bl)) b3 (polar b2 0 (-(* 4 bl))) b4 (polar a3 (/ pi 2) (* 3 bl)) b5 (polar a4 (/ pi 2) (* 1 bl)) b6 (polar b5 pi (-(* 4 bl))))
  (command "pline" a2 "w" (* 0.2 bl) "" b1 b2 b3 b4 b6 b5 a4 "") (setq sss (entlast))
  (command "pedit" "m" s ss sss "" "j" "" "")))
  (setvar "osmode" 15359)
  (command "ucs" ""))
