(defun c:zz()
  (setvar "cmdecho" 0)
  (setq p1 (getpoint "\nµã1\n") p2 (getpoint "\nµã2\n"))
  (command "line" p1 p2 "") (setq x (entlast))
  (command "UCS" "ob" x)
  (command "erase" x "")
  (setq a1 (getpoint "\nµã1\n") a2 (getpoint "\nµã2\n") a3 (getpoint "\nµã3\n"))
  (command "dimlinear" a1 a2 a3)
  (setq b1 1)
  (while (/= b1 nil) 
    (setq b1 nil)
    (setq b1 (getpoint "\nµã\n"))
    (command "dimcontinue" b1 "" "") (setq bz (entlast)))
  (command "UCS" "")
  (prin1))
