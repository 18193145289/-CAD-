(defun c:zh()
  (setq dia_id (load_dialog "D:\\蒋子英工作与划水\\lsp和dcl练习\\桩号.DCL"))
  (new_dialog "zh" dia_id)
  (action_tile "accept" "(zh1)")
  (start_dialog) (unload_dialog dia_id)
  (draw))
(defun zh1()
  (setq osm "osmode")
  (setvar "osmode" 0)
  (setq bh (get_tile "bh") bhs (strlen bh) bl (atoi (get_tile "bl")))
  (cond ((= bl 0) (setq bl 30))
	((= bl 1) (setq bl 50))
	((= bl 2) (setq bl 100))
	((= bl 3) (setq bl 150))
	((= bl 4) (setq bl 200))
	((= bl 5) (setq bl 250))
	((= bl 6) (setq bl 300))))
(defun draw()
  (setq a (getpoint "选一点：\n"))
  (setq b (polar a 0 (* 6 bl)))
  (command "ellipse" a b (* 1.5 bl)) (setq i1 (entlast))
  (if (= bhs 1)
  	(setq c (polar a 0 (* 2.375 bl)) c (polar c (/ (* 3 pi) 2) (* 1.25 bl)))
        (setq c (polar a 0 (* 1.75 bl)) c (polar c (/ (* 3 pi) 2) (* 1.25 bl))))
  (command "text" c (* 2.5 bl) 0 bh) (setq i2 (entlast))
  (setq d (polar a 0 (* 3 bl)) d (polar d (/ (* 3 pi) 2) (* 1.5 bl)) e (polar d (/ (* 3 pi) 2) (* 6 bl)))
  (command "line" d e "") (setq i3 (entlast))
  (setq i3 (entget i3) i3 (cons (cons 62 1) i3) i3 (cons (cons 6 "CENTER") i3))
  (entmod i3) (setq i3 (entlast))
  (command "move" i1 i2 i3 "" e (getpoint "选择移动位置：\n"))
  (setvar "osmode" osm)
  (prin1)
  )
