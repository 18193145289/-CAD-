;;;(defun c:zzz()
;;;  (setvar "cmdecho" 0)
;;;  (setq a1 (getpoint"1:\n") b1 (polar a1 (/ pi 2) 10) c1 (polar b1 0 8))
;;;;;;;;;	a2 (getpoint"2:\n") a3 (getpoint"3:\n") a4 (getpoint"4:\n") a5 (getpoint"5:\n") a6 (getpoint"6:\n") a7 (getpoint"7:\n") a8 (getpoint"8:\n") a9 (getpoint"9:\n") a10 (getpoint"10:\n") a11 (getpoint"11:\n") a12 (getpoint"12:\n"))
;;;  (setq x1 (rtos (car a1) 2 3) y1 (rtos (cadr a1) 2 3))
;;;;;;;;;	x2 (rtos (car a2) 2 3) y2 (rtos (cadr a2) 2 3) x3 (rtos (car a3) 2 3) y3 (rtos (cadr a3) 2 3) x4 (rtos (car a4) 2 3) y4 (rtos (cadr a4) 2 3) x5 (rtos (car a5) 2 3) y5 (rtos (cadr a5) 2 3) x6 (rtos (car a6) 2 3) y6 (rtos (cadr a6) 2 3) x7 (rtos (car a7) 2 3) y7 (rtos (cadr a7) 2 3) x8 (rtos (car a8) 2 3) y8 (rtos (cadr a8) 2 3) x9 (rtos (car a9) 2 3) y9 (rtos (cadr a9) 2 3) x10 (rtos (car a10) 2 3) y10 (rtos (cadr a10) 2 3) x11 (rtos (car a11) 2 3) y11 (rtos (cadr a11) 2 3) x12 (rtos (car a12) 2 3) y12 (rtos (cadr a12) 2 3))
;;;  (setq b11 (polar b1 (/ pi 2) 0.1)) (setq b12 (polar b1 (/ (* 3 pi) 2) 1.5))
;;;;;;;;;	a21 (polar a2 (/ (* 3 pi) 2) 2.5) a31 (polar a3 (/ (* 3 pi) 2) 2.5) a41 (polar a4 (/ (* 3 pi) 2) 2.5) a51 (polar a5 (/ (* 3 pi) 2) 2.5) a61 (polar a6 (/ (* 3 pi) 2) 2.5) a71 (polar a7 (/ (* 3 pi) 2) 2.5) a81 (polar a8 (/ (* 3 pi) 2) 2.5) a91 (polar a9 (/ (* 3 pi) 2) 2.5) a101 (polar a10 (/ (* 3 pi) 2) 2.5) a111 (polar a11 (/ (* 3 pi) 2) 2.5) a121 (polar a12 (/ (* 3 pi) 2) 2.5))
;;;  (command "pline" a1 b1 c1 "") (command "text" b11 1.5 0 "X=" "text" b12 1.5 0 "Y=")
;;;  (setq b21 (polar b11 0 1.7) b22 (polar b12 0 1.7))
;;;  (command "text" b21 1.5 0 y1) (command "text" b22 1.5 0 x1 ))
;;;;;;  (command "text" a2 2.5 0 x2 "") (command "text" a21 2.5 0 y2 "") (command "text" a3 2.5 0 x3 "") (command "text" a31 2.5 0 y3 "") (command "text" a4 2.5 0 x4 "") (command "text" a41 2.5 0 y4 "") (command "text" a5 2.5 0 x5 "") (command "text" a51 2.5 0 y5 "") (command "text" a6 2.5 0 x6 "") (command "text" a61 2.5 0 y6 "") (command "text" a7 2.5 0 x7 "") (command "text" a71 2.5 0 y7 "") (command "text" a8 2.5 0 x8 "") (command "text" a81 2.5 0 y8 "") (command "text" a9 2.5 0 x9 "") (command "text" a91 2.5 0 y9 "") (command "text" a10 2.5 0 x10 "") (command "text" a101 2.5 0 y10 "") (command "text" a11 2.5 0 x11 "") (command "text" a111 2.5 0 y11 "") (command "text" a12 2.5 0 x12 "") (command "text" a121 2.5 0 y12 ""))

;;;;;;(defun c:zzz()
;;;;;;  (setq o (getvar "osmode"))
;;;;;;  (setvar "osmode" 1028)
;;;;;;  (setq a1 (getpoint"d:\n") bg (getfiled "新建文件" "" "xls" 1) dbg (open bg "w"))
;;;;;;  (close dbg)
;;;;;;  (while (/= a1 nil)
;;;;;;    (setq a2 (polar a1 (* 3 (/ pi 2)) 5) a3 (polar a2 0 12) b2 (polar a2 (/ pi 2) 0.1) b3 (polar a2 (* 3 (/ pi 2)) 2.5) c2 (polar b2 0 3) c3 (polar b3 0 3))
;;;;;;    (command "pline" a1 a2 a3 "")
;;;;;;    (command "text" b2 2.5 0 "X=" "text" b3 2.5 0 "Y=")
;;;;;;    (setq x (rtos (car a1) 2 3) y (rtos (cadr a1) 2 3))
;;;;;;    (command "text" c2 2.5 0 x "text" c3 2.5 0 y)
;;;;;;    (setq dbg (open bg "a"))
;;;;;;    (princ x dbg) (princ "," dbg) (princ y dbg) (princ "\n" dbg)
;;;;;;    (close dbg)
;;;;;;    (setq a1 (getpoint"d:\n")))
;;;;;;  (setvar "osmode" o)
;;;;;;    (prin1))

;;;(defun c:zzz()
;;;  (setvar "cmdecho" 0)
;;;  (setq o (getvar "osmode"))
;;;  (setvar "osmode" 0)
;;;  (setq ss (ssget '((0 . "CIRCLE"))) n 0 bg (getfiled "新建文件" "" "xls" 1) dbg (open bg "w"))
;;;  (close dbg)
;;;  (while (/= ss nil)
;;;    (setq l (sslength ss))
;;;    (repeat l
;;;    	(setq s (entget (ssname ss n)) s (assoc 10 s) x (cadr s) y (caddr s))
;;;    	(setq a1 (list x y))
;;;    	(setq a2 (polar a1 (* 11 (/ pi 6)) 20) a3 (polar a2 0 12) b2 (polar a2 (/ pi 2) 0.1) b3 (polar a2 (* 3 (/ pi 2)) 2.5) c2 (polar b2 0 3) c3 (polar b3 0 3))
;;;    	(command "pline" a1 a2 a3 "")
;;;    	(command "text" b2 2.5 0 "X=" "text" b3 2.5 0 "Y=")
;;;    	(setq x (rtos (car a1) 2 3) y (rtos (cadr a1) 2 3))
;;;    	(command "text" c2 2.5 0 x "text" c3 2.5 0 y)
;;;    	(setq dbg (open bg "a"))
;;;    	(princ x dbg) (princ "," dbg) (princ y dbg) (princ "\n" dbg)
;;;    	(close dbg)
;;;    (setq n (+ n 1))))
;;;  (setvar "osmode" o)
;;;  (prin1))


(defun c:zz()
  (setvar "osmode" 0)
  (setq dig_id (load_dialog "Z:\\划水\\lsp和dcl练习\\绝对坐标.DCL"))
  (new_dialog "jdzb" dig_id)
  (start_image "i")
  (slide_image 0 0 (dimx_tile "i") (dimy_tile "i") "Z:\\划水\\lsp和dcl练习\\绝对坐标.sld")
  (end_image)
  (action_tile "accept" "(hdz) (done_dialog 1)")
  (action_tile "cancel" "(done_dialog 0)")
  (setq st (start_dialog)) (unload_dialog dig_id)
  (if (= st 1) (draw))
  (prin1))
(defun hdz()
  (setq wz (atof (get_tile "wz"))
	b (atoi (get_tile "b"))))
(defun draw()
  (cond ((= b 0) (setq b 90))
	((= b 1) (setq b 60))
	((= b 2) (setq b 45))
	((= b 3) (setq b 30))
	((= b 4) (setq b 20))
	((= b 5) (setq b 0))
	((= b 6) (setq b -90))
	((= b 7) (setq b -60))
	((= b 8) (setq b -45))
	((= b 9) (setq b -30))
	((= b 10) (setq b -20)))
  (setq ss (ssget '((0 . "CIRCLE"))) n 0 bg (getfiled "新建文件" "" "xls" 1) dbg (open bg "w"))
  (close dbg)
  (setq l (sslength ss))
  (while (< n l)
    (repeat l
    	(setq s (entget (ssname ss n)) s (assoc 10 s) x (cadr s) y (caddr s))
    	(setq a1 (list x y) w1 (* 6 wz) w2 (* (* (/ wz 2.5) 1.5) 2))
    	(setq a2 (polar a1 (/ (* b pi) 180) w2) a3 (polar a2 0 w1) b2 (polar a2 (/ pi 2) 0.1) b3 (polar a2 (* 3 (/ pi 2)) wz) c2 (polar b2 0 w2) c3 (polar b3 0 w2))
    	(command "pline" a1 a2 a3 "")
    	(command "text" b2 wz 0 "X=" "text" b3 wz 0 "Y=")
    	(setq x (rtos (car a1) 2 3) y (rtos (cadr a1) 2 3))
    	(command "text" c2 wz 0 Y "text" c3 wz 0 X)
    	(setq dbg (open bg "a"))
    	(princ x dbg) (princ "," dbg) (princ y dbg) (princ "\n" dbg)
    	(close dbg)
    (setq n (+ n 1))))
  (setq o (setvar "osmode" 15359))
  (prin1))
;;;  (setq r (* 2.5 b))
;;;  (command "text" a r 0 wz)
;;;  (setq ws (strlen wz)
;;;	r1 (* (/ (sqrt 2) 2) r))
;;;  (setq wz (entlast) wz (entget wz) wz (cons (cons 62 3) wz)) (entmod wz)
;;;  (cond ((= ws 1) (setq c (polar a (/ pi 4) r) r (+ r1 (* 0.2 b))))
;;;	((= ws 2) (setq c (polar a (/ pi 4) r) r(+ r1 (* 0.2 b))))
;;;	((= ws 3) (setq c (polar (polar a 0 (* (/ ws 2) (+ (* 0.5 b) (/ r 2)))) (/ pi 2) (* (/ ws 2) (/ r 2))) r (* (/ ws 2) r)))
;;;	((= ws 4) (setq c (polar (polar a 0 (* (/ ws 2) (/ r 2))) (/ pi 2) (* 0.5 (/ ws 2) (/ r 2))) r (* (/ ws 2) r))))
;;;  (command "circle" c r)
;;;  (setq cc (entlast) cc (entget cc) cc (cons (cons 62 3) cc)) (entmod cc)
;;;  (if (= sy 1) (cond ((= s 1) (syx))
;;;		     ((= x 1) (xyx))
;;;		     ((= z 1) (zyx))
;;;		     ((= y 1) (yyx))))
;;;)
;;;(defun syx()
;;;  (setq c1 (polar c (/ pi 2) r)
;;;	c2 (polar c1 (/ pi 2) r)
;;;	c3 (polar c2 0 r))
;;;  (command "line" c1 c2 "")
;;;  (setq z1 (entlast) z1 (entget z1) z1 (cons (cons 62 3) z1)) (entmod z1)
;;;  (command "line" c2 c3 "")
;;;  (setq z2 (entlast) z2 (entget z2) z2 (cons (cons 62 3) z2)) (entmod z2)
;;;  )				  
;;;(defun xyx()
;;;  (setq c1 (polar c (* 3 (/ pi 2)) r)
;;;	c2 (polar c1 (* 3 (/ pi 2)) r)
;;;	c3 (polar c2 0 r))
;;;  (command "line" c1 c2 "")
;;;  (setq z1 (entlast) z1 (entget z1) z1 (cons (cons 62 3) z1)) (entmod z1)
;;;  (command "line" c2 c3 "")
;;;  (setq z2 (entlast) z2 (entget z2) z2 (cons (cons 62 3) z2)) (entmod z2)
;;;  )
;;;(defun zyx()
;;;  (setq c1 (polar c pi r)
;;;	c2 (polar c1 pi r)
;;;	c3 (polar c2 (* 1.5 pi) r))
;;;  (command "line" c1 c2 "")
;;;  (setq z1 (entlast) z1 (entget z1) z1 (cons (cons 62 3) z1)) (entmod z1)
;;;  (command "line" c2 c3 "")
;;;  (setq z2 (entlast) z2 (entget z2) z2 (cons (cons 62 3) z2)) (entmod z2)
;;;  )
;;;(defun yyx()
;;;  (setq c1 (polar c 0 r)
;;;	c2 (polar c1 0 r)
;;;	c3 (polar c2 (* 1.5 pi) r))
;;;  (command "line" c1 c2 "")
;;;  (setq z1 (entlast) z1 (entget z1) z1 (cons (cons 62 3) z1)) (entmod z1)
;;;  (command "line" c2 c3 "")
;;;  (setq z2 (entlast) z2 (entget z2) z2 (cons (cons 62 3) z2)) (entmod z2)
;;;  )
