(defun c:1()
  (setvar "cmdecho" 0)
  (command "color" 7)
  (setq dialog_id (load_dialog "Z:\划水\lsp和dcl练习\\斑马线.DCL"))
  (new_dialog "bmx" dialog_id)
  (action_tile "accept" "(hqz)")
  (start_dialog) (unload_dialog dialog_id)
  (draw))
(defun hqz()
  (setq d (atoi (get_tile "d")) bc (atoi (get_tile "bc"))))
(defun draw()
  (setq a1 (getpoint "\n请选择第一点:\n") b1 (getpoint "\n请选择第二点:\n"))
  (command "line" a1 b1 "") (setq i1 (entlast))
  (setq z1 (getpoint "\n作平行线:\n请选择直线第一点:\n") z2 (getpoint "\n请选择直线第二点:\n"))
  (command "line" z1 z2 "") (setq x (entlast))
  (command "UCS" "ob" x)
  (command "copy" i1 "" a1 "@10,0") (setq m (entlast))
  (command "UCS" "w")
  (setq p1 (list (cadr (assoc 10 (entget m))) (caddr (assoc 10 (entget m)))))
  (command "offset" d i1 p1 "") (setq i2 (entlast))
  (setq a2 (list (cadr (assoc 10 (entget i2))) (caddr (assoc 10 (entget i2)))) b2 (list (cadr (assoc 11 (entget i2))) (caddr (assoc 11 (entget i2)))))
  (command "UCS" "ob" x)
  (cond ((= bc 6)
   (command "copy" i2 "" a2 "@6,0") (setq i3 (entlast)))
	((= bc 5)
   (command "copy" i2 "" a2 "@5,0") (setq i3 (entlast)))
	((= bc 4)
   (command "copy" i2 "" a2 "@4,0") (setq i3 (entlast)))
	((= bc 3)
   (command "copy" i2 "" a2 "@3,0") (setq i3 (entlast)))
	((= bc 7)
   (command "copy" i2 "" a2 "@7,0") (setq i3 (entlast)))
	((= bc 8)
   (command "copy" i2 "" a2 "@8,0") (setq i3 (entlast)))
	((= bc 9)
   (command "copy" i2 "" a2 "@9,0") (setq i3 (entlast)))
	((= bc 10)
   (command "copy" i2 "" a2 "@10,0") (setq i3 (entlast))))
  (command "UCS" "w")
  (setq a3 (list (cadr (assoc 10 (entget i3))) (caddr (assoc 10 (entget i3)))) b3 (list (cadr (assoc 11 (entget i3))) (caddr (assoc 11 (entget i3)))))
  (command "line" a2 a3 "") (setq pl (entlast))
  (command "pedit" pl "" "w" 0.4 "")
  (setq s (distance a3 b3) n (/ s 1) n (rtos n 2 0) n (atoi n))
  (command "UCS" "ob" i1)
  (repeat (+ n 1)
    (command "copy" pl "" a2 "@1,0") (setq pl (entlast)))
  (command "pedit" i1 "" "w" 0.4 "")
  (command "erase" i2 i3 m x "")
  (command "UCS" "w")
  (prin1))
