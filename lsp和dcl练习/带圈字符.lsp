(defun c:dqz()
  (setq osm (getvar "osmode"))
  (setvar "osmode" 0)
  (setq dig_id (load_dialog "C:\\Users\\Administrator\\Desktop\\lsp和dcl练习\\带圈字符.DCL"))
  (new_dialog "dqzf" dig_id)
  (start_image "i")
  (slide_image 0 0 (dimx_tile "i") (dimy_tile "i") "C:\\Users\\Administrator\\Desktop\\lsp和dcl练习\\带圈字符.sld")
  (end_image)
  (action_tile "accept" "(hdz) (done_dialog 1)")
  (action_tile "cancel" "(done_dialog 0)")
  (action_tile "sy" "(hdz)")
  (action_tile "fy" "(hdz)")
  (setq st (start_dialog)) (unload_dialog dig_id)
  (if (= st 1) (draw))
  (setvar "osmode" osm)
  (prin1))
(defun hdz()
  (setq wz (get_tile "wz")
        sy (atoi (get_tile "sy"))
	fy (atoi (get_tile "fy"))
	b (atoi (get_tile "b"))
	s (atoi (get_tile "s"))
	x (atoi (get_tile "x"))
	z (atoi (get_tile "z"))
	y (atoi (get_tile "y"))))
(defun draw()
  (setq a (getpoint "选一点："))
  (cond ((= b 0) (setq b 10))
	((= b 1) (setq b 20))
	((= b 2) (setq b 30))
	((= b 3) (setq b 35))
	((= b 4) (setq b 50))
	((= b 5) (setq b 80))
	((= b 6) (setq b 100))
	((= b 7) (setq b 150))
	((= b 8) (setq b 200))
	((= b 9) (setq b 300)))
  (setq r (* 2.5 b))
  (command "text" a r 0 wz)
  (setq ws (strlen wz)
	r1 (* (/ (sqrt 2) 2) r))
  (setq wz (entlast) wz (entget wz) wz (cons (cons 62 3) wz)) (entmod wz)
  (cond ((= ws 1) (setq c (polar a (/ pi 4) r) r (+ r1 (* 0.2 b))))
	((= ws 2) (setq c (polar a (/ pi 4) r) r(+ r1 (* 0.2 b))))
	((= ws 3) (setq c (polar (polar a 0 (* (/ ws 2) (+ (* 0.5 b) (/ r 2)))) (/ pi 2) (* (/ ws 2) (/ r 2))) r (* (/ ws 2) r)))
	((= ws 4) (setq c (polar (polar a 0 (* (/ ws 2) (/ r 2))) (/ pi 2) (* 0.5 (/ ws 2) (/ r 2))) r (* (/ ws 2) r))))
  (command "circle" c r)
  (setq cc (entlast) cc (entget cc) cc (cons (cons 62 3) cc)) (entmod cc)
  (if (= sy 1) (cond ((= s 1) (syx))
		     ((= x 1) (xyx))
		     ((= z 1) (zyx))
		     ((= y 1) (yyx))))
)
(defun syx()
  (setq c1 (polar c (/ pi 2) r)
	c2 (polar c1 (/ pi 2) r)
	c3 (polar c2 0 r))
  (command "line" c1 c2 "")
  (setq z1 (entlast) z1 (entget z1) z1 (cons (cons 62 3) z1)) (entmod z1)
  (command "line" c2 c3 "")
  (setq z2 (entlast) z2 (entget z2) z2 (cons (cons 62 3) z2)) (entmod z2)
  )				  
(defun xyx()
  (setq c1 (polar c (* 3 (/ pi 2)) r)
	c2 (polar c1 (* 3 (/ pi 2)) r)
	c3 (polar c2 0 r))
  (command "line" c1 c2 "")
  (setq z1 (entlast) z1 (entget z1) z1 (cons (cons 62 3) z1)) (entmod z1)
  (command "line" c2 c3 "")
  (setq z2 (entlast) z2 (entget z2) z2 (cons (cons 62 3) z2)) (entmod z2)
  )
(defun zyx()
  (setq c1 (polar c pi r)
	c2 (polar c1 pi r)
	c3 (polar c2 (* 1.5 pi) r))
  (command "line" c1 c2 "")
  (setq z1 (entlast) z1 (entget z1) z1 (cons (cons 62 3) z1)) (entmod z1)
  (command "line" c2 c3 "")
  (setq z2 (entlast) z2 (entget z2) z2 (cons (cons 62 3) z2)) (entmod z2)
  )
(defun yyx()
  (setq c1 (polar c 0 r)
	c2 (polar c1 0 r)
	c3 (polar c2 (* 1.5 pi) r))
  (command "line" c1 c2 "")
  (setq z1 (entlast) z1 (entget z1) z1 (cons (cons 62 3) z1)) (entmod z1)
  (command "line" c2 c3 "")
  (setq z2 (entlast) z2 (entget z2) z2 (cons (cons 62 3) z2)) (entmod z2)
  )
